#usage "update current libary with reference package library<p>"
       "<author>Author alf@cadsoft.de</author>"

string referencepackage = "plcc-socket.lbr";
string cmd = "";

library(L) {
  if (filename(L.name) == referencepackage);
  else sprintf(cmd, "UPDATE %s;\nWRITE;\n", referencepackage);
}
exit(cmd);
